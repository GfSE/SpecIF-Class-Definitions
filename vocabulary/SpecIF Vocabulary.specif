# SpecIF Vocabulary
The SpecIF Vocabulary (or Glossary) collects terms used in the domain of systems engineering and requirements management. Agreed-upon terms help both collaborators to communicate more clearly and systems to match data fields automatically.
- Rights: Creative Commons 4.0 CC BY-SA, https://creativecommons.org/licenses/by-sa/4.0/

## SpecIF Vocabulary (SpecIF:Outline)

## Value Terms (SpecIF:Heading)
- dcterms:description: These are terms for certain enumerated property values. Not only the property titles, but also any enumerated value must be mapped between different systems or domains; therefore using defined terms is beneficial. Of course, like any other vocabulary term, any term used as property value for transmission or storage can be translated for display.
  This is still experimental. Please let us know what you think: Dr. Oskar von Dungern.

## bpmn:timer (SpecIF:TermPropertyValue)
- dcterms:description: A defined value for the [[dcterms:type]] property of [[FMC:Actor]] when used to represent a 'Timer' element in models created with BPMN.
- SpecIF:Status: experimental

## bpmn:join (SpecIF:TermPropertyValue)
- dcterms:description: A defined value for the [[dcterms:type]] property of [[FMC:Actor]] when used to represent a 'Join' element in models created with BPMN.
- SpecIF:Status: experimental

## bpmn:processStep (SpecIF:TermPropertyValue)
- dcterms:description: A defined value for the [[dcterms:type]] property of [[FMC:Actor]] when used to represent a process step.
- SpecIF:Status: experimental

## bpmn:endEvent (SpecIF:TermPropertyValue)
- dcterms:description: A defined value for the [[dcterms:type]] property of [[FMC:Event]] when used to represent a general end event.
- SpecIF:Origin: https://camunda.com/bpmn/reference/
- SpecIF:Status: experimental

## bpmn:intermediateEvent (SpecIF:TermPropertyValue)
- dcterms:description: A defined value for the [[dcterms:type]] property of [[FMC:Event]] when used to represent a general intermediate event.
- SpecIF:Origin: https://camunda.com/bpmn/reference/
- SpecIF:Status: experimental

## bpmn:startEvent (SpecIF:TermPropertyValue)
- dcterms:description: A defined value for the [[dcterms:type]] property of [[FMC:Event]] when used to represent a general start event.
- SpecIF:Origin: https://camunda.com/bpmn/reference/
- SpecIF:Status: experimental

## SpecIF:UserRole (SpecIF:TermPropertyValue)
- dcterms:description: This is a subclass of [[FMC:Actor]]; more precisely a value of it's property [[dcterms:type]].
- SpecIF:Status: experimental

## IREB:Stakeholder (SpecIF:TermPropertyValue)
- dcterms:description: A person or organization that has a (direct or indirect) influence on a system’s requirements. Indirect influence also includes situations where a person or organization is impacted by the system.
  This is a subclass of [[FMC:Actor]], more precisely a value of it's property [[dcterms:type]].
- SpecIF:Origin: https://www.ireb.org/content/downloads/1-cpre-glossary/ireb_cpre_glossary_17.pdf
- SpecIF:Status: SpecIF:LifecycleStatusReleased

## IREB:RequirementTypeConstraint (SpecIF:TermPropertyValue)
- dcterms:description: A [[IREB:Requirement]] that limits the solution space beyond what is necessary for meeting the given functional requirements and quality requirements.
- SpecIF:Origin: https://www.ireb.org/content/downloads/1-cpre-glossary/ireb_cpre_glossary_17.pdf
- SpecIF:Status: equivalent

## IREB:RequirementTypeQuality (SpecIF:TermPropertyValue)
- dcterms:description: A [[IREB:Requirement]] that pertains to a quality concern that is not covered by functional requirements.
- SpecIF:Origin: https://www.ireb.org/content/downloads/1-cpre-glossary/ireb_cpre_glossary_17.pdf
- SpecIF:Status: equivalent

## IREB:RequirementTypeFunction (SpecIF:TermPropertyValue)
- dcterms:description: A requirement concerning a result of behavior that shall be provided by a functionof a system(or of a component or service).
- SpecIF:Origin: https://www.ireb.org/content/downloads/1-cpre-glossary/ireb_cpre_glossary_17.pdf
- SpecIF:Status: equivalent

## IREB:Constraint (SpecIF:TermPropertyValue)
- dcterms:description: A [[IREB:Requirement]] that limits the solution space beyond what is necessary for meeting the given functional requirements and quality requirements.
- SpecIF:Origin: https://www.ireb.org/content/downloads/1-cpre-glossary/ireb_cpre_glossary_17.pdf
- SpecIF:Status: SpecIF:LifecycleStatusReleased

## IREB:QualityRequirement (SpecIF:TermPropertyValue)
- dcterms:description: A [[IREB:Requirement]] that pertains to a quality concern that is not covered by functional requirements.
- SpecIF:Origin: https://www.ireb.org/content/downloads/1-cpre-glossary/ireb_cpre_glossary_17.pdf
- SpecIF:Status: SpecIF:LifecycleStatusReleased

## IREB:FunctionalRequirement (SpecIF:TermPropertyValue)
- dcterms:description: A [[IREB:Requirement]] concerning a result of behavior that shall be provided by a functionof a system(or of a component or service).
- SpecIF:Origin: https://www.ireb.org/content/downloads/1-cpre-glossary/ireb_cpre_glossary_17.pdf
- SpecIF:Status: SpecIF:LifecycleStatusReleased

## SpecIF:LifecycleStatusWithdrawn (SpecIF:TermPropertyValue)
- dcterms:description: A lifecycle status of a development artefact.
- SpecIF:Status: experimental

## SpecIF:LifecycleStatusDeprecated (SpecIF:TermPropertyValue)
- dcterms:description: A lifecycle status of a development artefact.
- SpecIF:Status: experimental

## SpecIF:LifecycleStatusReleased (SpecIF:TermPropertyValue)
- dcterms:description: A lifecycle status of a development artefact.
- SpecIF:Status: experimental

## SpecIF:LifecycleStatusValidated (SpecIF:TermPropertyValue)
- dcterms:description: A lifecycle status of a development artefact.
- SpecIF:Status: experimental

## SpecIF:LifecycleStatusDone (SpecIF:TermPropertyValue)
- dcterms:description: A lifecycle status of a development artefact. Meets the requirements of the "Definition of Done" of the agile development method.
- SpecIF:Status: experimental

## SpecIF:LifecycleStatusReady (SpecIF:TermPropertyValue)
- dcterms:description: A lifecycle status of a development artefact. Meets the requirements of the "Definition of Ready" of the agile development method.
- SpecIF:Status: experimental

## SpecIF:LifecycleStatusApproved (SpecIF:TermPropertyValue)
- dcterms:description: A lifecycle status of a development artefact.
- SpecIF:Status: experimental

## SpecIF:LifecycleStatusSubmitted (SpecIF:TermPropertyValue)
- dcterms:description: A lifecycle status of a development artefact.
- SpecIF:Status: experimental

## SpecIF:LifecycleStatusDrafted (SpecIF:TermPropertyValue)
- dcterms:description: A lifecycle status of a development artefact.
- SpecIF:Status: experimental

## SpecIF:LifecycleStatusInitial (SpecIF:TermPropertyValue)
- dcterms:description: A lifecycle status of a development artefact.
- SpecIF:Status: experimental

## SpecIF:LifecycleStatusRejected (SpecIF:TermPropertyValue)
- dcterms:description: A lifecycle status of a development artefact.
- SpecIF:Status: experimental

## SpecIF:sizeXS (SpecIF:TermPropertyValue)
- dcterms:description: T-shirt sizes have become popular to classify [[IREB:Risk]], [[SpecIF:Damage]] or similar. Translates to 'very small' in English.
- SpecIF:Origin: http://specif.de
- SpecIF:Status: experimental

## SpecIF:sizeS (SpecIF:TermPropertyValue)
- dcterms:description: T-shirt sizes have become popular to classify [[IREB:Risk]], [[SpecIF:Damage]] or similar. Translates to 'small' in English.
- SpecIF:Origin: http://specif.de
- SpecIF:Status: experimental

## SpecIF:sizeM (SpecIF:TermPropertyValue)
- dcterms:description: T-shirt sizes have become popular to classify [[IREB:Risk]], [[SpecIF:Damage]] or similar. Translates to 'medium' in English.
- SpecIF:Origin: http://specif.de
- SpecIF:Status: experimental

## SpecIF:sizeL (SpecIF:TermPropertyValue)
- dcterms:description: T-shirt sizes have become popular to classify [[IREB:Risk]], [[SpecIF:Damage]] or similar. Translates to 'large' in English.
- SpecIF:Origin: http://specif.de
- SpecIF:Status: experimental

## SpecIF:sizeXL (SpecIF:TermPropertyValue)
- dcterms:description: T-shirt sizes have become popular to classify [[IREB:Risk]], [[SpecIF:Damage]] or similar. Translates to 'very large' in English.
- SpecIF:Origin: http://specif.de
- SpecIF:Status: experimental

## SpecIF:priorityLow (SpecIF:TermPropertyValue)
- dcterms:description: A value for property [[SpecIF:Priority]].
- SpecIF:Origin: http://specif.de
- Domain: Requirement Engineering, Automotive Stakeholder Request Clarification Process, System Model Integration, Agile Development
- SpecIF:Status: experimental

## SpecIF:priorityRatherLow (SpecIF:TermPropertyValue)
- dcterms:description: A value for property [[SpecIF:Priority]].
- SpecIF:Origin: http://specif.de
- Domain: Requirement Engineering, Automotive Stakeholder Request Clarification Process, System Model Integration, Agile Development
- SpecIF:Status: experimental

## SpecIF:priorityMedium (SpecIF:TermPropertyValue)
- dcterms:description: A value for property [[SpecIF:Priority]].
- SpecIF:Origin: http://specif.de
- Domain: Requirement Engineering, Automotive Stakeholder Request Clarification Process, System Model Integration, Agile Development
- SpecIF:Status: experimental

## SpecIF:priorityRatherHigh (SpecIF:TermPropertyValue)
- dcterms:description: A value for property [[SpecIF:Priority]].
- SpecIF:Origin: http://specif.de
- Domain: Requirement Engineering, Automotive Stakeholder Request Clarification Process, System Model Integration, Agile Development
- SpecIF:Status: experimental

## SpecIF:priorityHigh (SpecIF:TermPropertyValue)
- dcterms:description: A value for property [[SpecIF:Priority]].
- SpecIF:Origin: http://specif.de
- Domain: Requirement Engineering, Automotive Stakeholder Request Clarification Process, System Model Integration, Agile Development
- SpecIF:Status: experimental

## Property Terms (SpecIF:Heading)
- dcterms:description: A property carries information 'payload' and may be applied to resources or statements. The SpecIF terms listed in this chapter are used as property name/title, whereas the information is provided as 'value'. Usually a combination of complimentary properties is used per resource or statement class.
  A property corresponds to an 'ATTRIBUTE-DEFINITION' resp. 'ATTRIBUTE-VALUE' in the Requirements Interchange Format (ReqIF).

## HIS:SupplierStatus (SpecIF:TermProperty)
- SpecIF:Origin: Hersteller-Initiative Software
- SpecIF:Status: SpecIF:LifecycleStatusReleased

## HIS:SupplierComment (SpecIF:TermProperty)
- SpecIF:Origin: Hersteller-Initiative Software
- SpecIF:Status: SpecIF:LifecycleStatusReleased

## HIS:OemStatus (SpecIF:TermProperty)
- SpecIF:Origin: Hersteller-Initiative Software
- SpecIF:Status: SpecIF:LifecycleStatusReleased

## HIS:OemComment (SpecIF:TermProperty)
- SpecIF:Origin: Hersteller-Initiative Software
- SpecIF:Status: SpecIF:LifecycleStatusReleased

## SpecIF:OrdinalMark (SpecIF:TermProperty)
- dcterms:description: A string to determine the ordering of elements. Rules:
  - For ordering, only alphanumeric characters are permissible. A letter case has no effect; for example, 'F' is equivalent to 'f'.
  - The ordering at character level is alphanumeric, i.e. '1' < '7' < 'D' < 'X'.
  - Single character substrings < two-character substrings < substrings with more characters, thus '9' < '12' < '114'.
  - The ordinal mark may be separated by non-alphanumeric characters. All separators are equivalent; e.g. '-' is equivalent to ';' or '/'.
  - Each alphanumeric substring is used for ordering on its hierarchical level; the leftmost substring is most significant for the overall ordering.
  - For example '1' < '1.2' < '1.Y' < '1.1a' < '1-1b' < '1-1C' < '2'.
  A regular expression for extracting the substrings of an ordinal mark is /([0-9a-z]+)[^0-9a-z]{0,1}/gi.
- SpecIF:Origin: http://specif.de
- SpecIF:Status: experimental

## SpecIF:FitCriteria (SpecIF:TermProperty)
- SpecIF:Origin: http://specif.de
- SpecIF:Status: SpecIF:LifecycleStatusReleased

## SpecIF:Target (SpecIF:TermProperty)
- dcterms:description: The object of a subject-predicate-object statement.
- SpecIF:Origin: http://specif.de
- SpecIF:Status: SpecIF:LifecycleStatusDeprecated

## SpecIF:Object (SpecIF:TermProperty)
- dcterms:description: The object of a subject-predicate-object statement. Corresponds to a 'target' in ReqIF terminology.
- SpecIF:Origin: http://specif.de
- SpecIF:Status: SpecIF:LifecycleStatusReleased

## SpecIF:Source (SpecIF:TermProperty)
- dcterms:description: The subject of a subject-predicate-object statement.
- SpecIF:Origin: http://specif.de
- SpecIF:Status: SpecIF:LifecycleStatusDeprecated

## SpecIF:Subject (SpecIF:TermProperty)
- dcterms:description: The subject of a subject-predicate-object statement. Corresponds to a 'source' in ReqIF terminology.
- SpecIF:Origin: http://specif.de
- SpecIF:Status: SpecIF:LifecycleStatusReleased

## SpecIF:Origin (SpecIF:TermProperty)
- dcterms:description: The origin (source, reference) of an information or requirement
- SpecIF:Origin: http://specif.de
- SpecIF:Status: SpecIF:LifecycleStatusReleased

## SpecIF:Creation (SpecIF:TermProperty)
- dcterms:description: "manual": user interface supports creation, update and deletion of the resource.
  "auto": the resource is created, updated or deleted by an algorithm.
- SpecIF:Origin: http://specif.de
- SpecIF:Status: SpecIF:LifecycleStatusDeprecated

## SpecIF:Instantiation (SpecIF:TermProperty)
- dcterms:description: "user": a user creates, updates and deletes a resource's instance manually.
  "auto": a resource's instance is created, updated or deleted by an algorithm.
- SpecIF:Origin: http://specif.de
- SpecIF:Status: SpecIF:LifecycleStatusReleased

## SpecIF:Tag (SpecIF:TermProperty)
- SpecIF:Origin: http://specif.de
- SpecIF:Status: SpecIF:LifecycleStatusReleased

## SpecIF:Icon (SpecIF:TermProperty)
- dcterms:description: An icon associated with the resource class.
- SpecIF:Origin: http://specif.de
- SpecIF:Status: SpecIF:LifecycleStatusReleased

## SpecIF:Damage (SpecIF:TermProperty)
- SpecIF:Origin: http://specif.de
- SpecIF:Status: SpecIF:LifecycleStatusReleased

## SpecIF:Benefit (SpecIF:TermProperty)
- SpecIF:Origin: http://specif.de
- SpecIF:Status: SpecIF:LifecycleStatusReleased

## SpecIF:DueDate (SpecIF:TermProperty)
- dcterms:description: A 'Due Date' for the resource.
- SpecIF:Origin: http://specif.de
- SpecIF:Status: SpecIF:LifecycleStatusReleased

## SpecIF:Milestone (SpecIF:TermProperty)
- dcterms:description: A target 'Milestone' to implement the resource.
- SpecIF:Origin: http://specif.de
- SpecIF:Status: SpecIF:LifecycleStatusReleased

## SpecIF:Responsible (SpecIF:TermProperty)
- dcterms:description: The 'Person' being responsible for the resource.
- SpecIF:Origin: http://specif.de
- SpecIF:Status: SpecIF:LifecycleStatusReleased

## SpecIF:Priority (SpecIF:TermProperty)
- dcterms:description: The 'Priority' of the resource.
- SpecIF:Origin: http://specif.de
- SpecIF:Status: SpecIF:LifecycleStatusReleased

## SpecIF:Probability (SpecIF:TermProperty)
- SpecIF:Origin: http://specif.de
- SpecIF:Status: SpecIF:LifecycleStatusReleased

## SpecIF:LifecycleStatus (SpecIF:TermProperty)
- dcterms:description: The 'Lifecycle Status' of the resource.
- SpecIF:Origin: http://specif.de
- SpecIF:Status: SpecIF:LifecycleStatusReleased

## SpecIF:SubClass (SpecIF:TermProperty)
- dcterms:description: Describes the role or sub-type of a model-element. For example, a [[FMC:Actor]] may represent a System Function, a System Component or a User Role. Similarly, in the context of process modelling, a FMC:Actor may represent a Process Step or again a User Role. So, all of these are meaningful values for a FMC:Actor's property named SpecIF:SubClass.
- SpecIF:Origin: http://specif.de
- SpecIF:Status: SpecIF:LifecycleStatusDeprecated

## IREB:RequirementType (SpecIF:TermProperty)
- dcterms:description: Requirements are typically sub-classified into functional requirements ([[IREB:FunctionalRequirement]]), quality requirements ([[IREB:QualityRequirement]]) and constraints ([[IREB:Constraint]]). The latter two are also called non-functional requirements.
- SpecIF:Origin: https://www.ireb.org/content/downloads/1-cpre-glossary/ireb_cpre_glossary_17.pdf
- SpecIF:Status: experimental

## UML:Stereotype (SpecIF:TermProperty)
- dcterms:description: Describes the role or sub-type of a model-element. For example, a [[FMC:Actor]] may represent a System Function, a System Component or a User Role. Similarly, in the context of process modelling, a FMC:Actor may represent a Process Step or again a User Role. So, all of these are meaningful values for a FMC:Actor's property named UML:Stereotype.
- SpecIF:Origin: http://specif.de
- SpecIF:Status: SpecIF:LifecycleStatusReleased

## SpecIF:Stereotype (SpecIF:TermProperty)
- dcterms:description: Describes the role or sub-type of a model-element. For example, a [[FMC:Actor]] may represent a System Function, a System Component or a User Role. Similarly, in the context of process modelling, a FMC:Actor may represent a Process Step or again a User Role. So, all of these are meaningful values for a FMC:Actor's property named SpecIF:Stereotype.
- SpecIF:Origin: http://specif.de
- SpecIF:Status: SpecIF:LifecycleStatusDeprecated

## dcterms:type (SpecIF:TermProperty)
- dcterms:description: The nature or genre of the resource. (source: DCMI)
  Recommended best practice is to use a controlled vocabulary such as the DCMI Type Vocabulary [DCMITYPE]. To describe the file format, physical medium, or dimensions of the resource, use the Format element.
  For example, a [[FMC:Actor]] may represent a System Function, a System Component or a User Role. Similarly, in the context of process modelling, a FMC:Actor may represent a Process Step or again a User Role. So, all of these are meaningful values for a FMC:Actor's property named dcterms:type.
- SpecIF:Origin: http://dublincore.org/specifications/
- SpecIF:Status: experimental

## SpecIF:Notation (SpecIF:TermProperty)
- dcterms:description: The notation used by a model diagram, e.g. 'BPMN 2.0', 'SysML Activity Diagram' or 'FMC Block Diagram'.
- SpecIF:Origin: http://specif.de
- SpecIF:Status: SpecIF:LifecycleStatusReleased

## SpecIF:Category (SpecIF:TermProperty)
- dcterms:description: The 'Category' (class) of the resource, usually with an enumerated value.
  Useful categories for requirements have been defined by the IREB, namely 'Function', 'Quality' and 'Constraint'.
- SpecIF:Origin: http://specif.de
- SpecIF:Status: SpecIF:LifecycleStatusReleased

## SpecIF:Type (SpecIF:TermProperty)
- SpecIF:Origin: http://specif.de
- SpecIF:Status: SpecIF:LifecycleStatusReleased

## oslc:instanceShape (SpecIF:TermProperty)
- dcterms:description: Resource Shape that provides hints as to resource property value-types and allowed values.
- SpecIF:Origin: http://open-services.net/bin/view/Main/RmSpecificationV2

## oslc:serviceProvider (SpecIF:TermProperty)
- dcterms:description: The scope of a resource is a URI for the resource's OSLC Service Provider.
- SpecIF:Origin: http://open-services.net/bin/view/Main/RmSpecificationV2

## oslc:shortTitle (SpecIF:TermProperty)
- dcterms:description: Short name identifying a resource, often used as an abbreviated identifier for presentation to end-users. SHOULD include only content that is valid inside an XHTML <span> element.
- SpecIF:Origin: http://open-services.net/bin/view/Main/RmSpecificationV2

## dcterms:rights (SpecIF:TermProperty)
- dcterms:description: Information about rights held in and over the resource. (source: DCMI)
- SpecIF:Origin: http://dublincore.org/specifications/
- SpecIF:Status: SpecIF:LifecycleStatusReleased

## dcterms:rightsHolder (SpecIF:TermProperty)
- dcterms:description: A person or organization owning or managing rights over the resource. (source: DCMI)
- SpecIF:Origin: http://dublincore.org/specifications/
- SpecIF:Status: SpecIF:LifecycleStatusReleased

## dcterms:contributor (SpecIF:TermProperty)
- dcterms:description: A resource responsible for making contributions to the resource. (source: DCMI)
- SpecIF:Origin: http://dublincore.org/specifications/
- SpecIF:Status: SpecIF:LifecycleStatusReleased

## SpecIF:changedAt (SpecIF:TermProperty)
- dcterms:description: Date/time on which the resource was changed last.
- SpecIF:Origin: http://specif.de
- SpecIF:Status: SpecIF:LifecycleStatusReleased

## dcterms:modified (SpecIF:TermProperty)
- dcterms:description: Timestamp last latest resource modification. (source: DCMI)
- SpecIF:Origin: http://dublincore.org/specifications/
- SpecIF:Status: equivalent

## SpecIF:changedBy (SpecIF:TermProperty)
- dcterms:description: The author who made the last modification.
- SpecIF:Origin: http://specif.de
- SpecIF:Status: SpecIF:LifecycleStatusReleased

## SpecIF:createdAt (SpecIF:TermProperty)
- dcterms:description: Date/time of creation of the resource.
- SpecIF:Origin: http://specif.de
- SpecIF:Status: SpecIF:LifecycleStatusReleased

## dcterms:created (SpecIF:TermProperty)
- dcterms:description: Timestamp of resource creation. (source: DCMI)
- SpecIF:Origin: http://dublincore.org/specifications/
- SpecIF:Status: equivalent

## SpecIF:createdBy (SpecIF:TermProperty)
- dcterms:description: A resource primarily responsible for making the resource.
- SpecIF:Origin: http://specif.de
- SpecIF:Status: SpecIF:LifecycleStatusReleased

## dcterms:creator (SpecIF:TermProperty)
- dcterms:description: An entity primarily responsible for making the resource. (source: DCMI)
  Creator(s) of resource (reference: Dublin Core). It is likely that the target resource will be a [[foaf:Person]] but that is not necessarily the case. (source: OSLC)
- SpecIF:Origin: http://dublincore.org/specifications/
- SpecIF:Status: equivalent

## dcterms:subject (SpecIF:TermProperty)
- dcterms:description: The topic of the resource. (source: DCMI)
  Tag or keyword for a resource. Each occurrence of a dcterms:subject property denotes an additional tag for the resource. (source: OSLC)
- SpecIF:Origin: http://dublincore.org/specifications/
- SpecIF:Status: SpecIF:LifecycleStatusReleased

## SpecIF:Id (SpecIF:TermProperty)
- dcterms:description: A unique reference to the resource within a given context.
- SpecIF:Origin: http://specif.de
- SpecIF:Status: SpecIF:LifecycleStatusDeprecated

## dcterms:identifier (SpecIF:TermProperty)
- dcterms:description: A unique reference to the resource within a given context. (source: DCMI)
  An identifier for a resource. This identifier may be unique with a scope that is defined by the RM provider. Assigned by the service provider when a resource is created. Not intended for end-user display. (source: OSLC)
- SpecIF:Origin: http://dublincore.org/specifications/
- SpecIF:Status: SpecIF:LifecycleStatusReleased

## dcterms:description (SpecIF:TermProperty)
- dcterms:description: An account of the resource. (source: DCMI)
  Descriptive text (reference: Dublin Core) about resource represented as rich text in XHTML content. SHOULD include only content that is valid and suitable inside an XHTML <div> element. (source: OSLC)
- SpecIF:Origin: http://dublincore.org/specifications/
- SpecIF:Status: SpecIF:LifecycleStatusReleased

## dcterms:title (SpecIF:TermProperty)
- dcterms:description: A name given to the resource. (source: DCMI)
  Title (reference: Dublin Core) of the resource represented as rich text in XHTML content. SHOULD include only content that is valid inside an XHTML <span> element. (source: OSLC)
- SpecIF:Origin: http://dublincore.org/specifications/
- SpecIF:Status: SpecIF:LifecycleStatusReleased

## Statement Class Terms (SpecIF:Heading)
- dcterms:description: A statement represents a logic affinity or association between two resources, i.e. system specification artefacts. The terms listed in this chapter may be used as predicates to distinguish different classes (types) of statements. Each statement class may define an individual set of properties for carrying the information 'payload'.
  In SpecIF, a statement is first order predicate logic. For each predicate (statement class), a list of eligible resource classes may be defined for subjects and objects, respectively. For example, the predicate [[oslc_rm:satisfies]] is usually confined to [[FMC:Actor]] and [[FMC:State]] as subject and [[IREB:Requirement]] as object.
  A statement consisting of subject-predicate-object (where a resource may serve as subject or object) can be directly mapped to a ReqIF relation, a RDF triple in OSLC or 'linked data' in general.
  A statement class corresponds to a 'SPEC-RELATION-TYPE' and a statement is a 'SPEC-RELATION' in the Requirements Interchange Format (ReqIF). In ArchiMate® 3.0, a statement is a Relationship.

## rdf:type (SpecIF:TermProperty)
- dcterms:description: rdf:type is an instance of rdf:Property that is used to state that a resource is an instance of a class.
  A triple of the form: R rdf:type C states that C is an instance of rdfs:Class and R is an instance of C.
  The rdfs:domain of rdf:type is rdfs:Resource. The rdfs:range of rdf:type is rdfs:Class.
- SpecIF:Origin: https://www.w3.org/TR/rdf-schema/#ch_type
- SpecIF:Status: SpecIF:LifecycleStatusReleased

## SpecIF:sameAs (SpecIF:TermStatementClass)
- dcterms:description: A resource represents the same entity as another resource.
- SpecIF:Origin: http://specif.de
- SpecIF:Status: equivalent

## owl:sameAs (SpecIF:TermStatementClass)
- dcterms:description: An owl:sameAs statement indicates that two URI references actually refer to the same thing: the individuals have the same "identity". (source: OWL)
- SpecIF:Origin: https://www.w3.org/TR/owl-ref
- SpecIF:Status: SpecIF:LifecycleStatusReleased

## SpecIF:isAntonymOf (SpecIF:TermStatementClass)
- dcterms:description: According to Wikipedia, "the term antonym (and the related antonymy) is commonly taken to be synonymous with opposite, but antonym also has other more restricted meanings. Graded (or gradable) antonyms are word pairs whose meanings are opposite and which lie on a continuous spectrum (_hot_, _cold_). Complementary antonyms are word pairs whose meanings are opposite but whose meanings do not lie on a continuous spectrum (_push_, _pull_). Relational antonyms are word pairs where opposite makes sense only in the context of the relationship between the two meanings (_teacher_, _pupil_)".
- SpecIF:Origin: https://en.wikipedia.org/wiki/Opposite_(semantics)
- SpecIF:Status: experimental

## SpecIF:isInverseOf (SpecIF:TermStatementClass)
- dcterms:description: A term is the inverse of another term.
  For example, a system 'B' contains a component '11', thus '11' isContainedBy 'B'.
- SpecIF:Origin: http://specif.de
- SpecIF:Status: SpecIF:LifecycleStatusDeprecated

## SpecIF:isSynonymOf (SpecIF:TermStatementClass)
- dcterms:description: A term is synonymous with another term, if both represent the same concept.
  According to Wikipedia, "a synonym is a word or phrase that means exactly or nearly the same as another word or phrase in the same language. Words that are synonyms are said to be synonymous".
- SpecIF:Origin: http://specif.de
- SpecIF:Status: SpecIF:LifecycleStatusReleased

## SpecIF:mentions (SpecIF:TermStatementClass)
- dcterms:description: A resource's text refers to another resorce (e.g. by hyper-link).
- SpecIF:Origin: http://specif.de
- SpecIF:Status: SpecIF:LifecycleStatusReleased

## SpecIF:commentRefersTo (SpecIF:TermStatementClass)
- dcterms:description: A [[SpecIF:Comment]] 'refers to' any other resource.
- SpecIF:Origin: http://specif.de
- SpecIF:Status: SpecIF:LifecycleStatusReleased

## SpecIF:refersTo (SpecIF:TermStatementClass)
- dcterms:description: A [[SpecIF:Comment]], [[SpecIF:Note]] or [[SpecIF:Issue]] 'refers to' any other resource.
- SpecIF:Origin: http://specif.de
- SpecIF:Status: SpecIF:LifecycleStatusReleased

## SpecIF:inheritsFrom (SpecIF:TermStatementClass)
- dcterms:description: A model-element class inherits from another. For example a data-object of class [[FMC:State]] inherits from another data-object, as shown in a UML Class Diagram).
- SpecIF:Origin: http://specif.de
- SpecIF:Status: experimental

## SysML:isGeneralizationOf (SpecIF:TermStatementClass)
- dcterms:description: An [[FMC:Actor]] is a generalization of another [[FMC:Actor]]; similarly for [[FMC:State]] and [[FMC:Event]].
- SpecIF:Origin: http://specif.de
- Domain: Vocabularies
- SpecIF:Status: SpecIF:LifecycleStatusReleased

## SysML:isSpecializationOf (SpecIF:TermStatementClass)
- dcterms:description: An [[FMC:Actor]] is a specialization of another [[FMC:Actor]]; similarly for [[FMC:State]] and [[FMC:Event]].
- SpecIF:Origin: http://specif.de
- Domain: Vocabularies
- SpecIF:Status: SpecIF:LifecycleStatusReleased

## SysML:includes (SpecIF:TermStatementClass)
- dcterms:description: An [[FMC:Actor]] <> includes another [[FMC:Actor]] <>.
- SpecIF:Origin: http://specif.de
- SpecIF:Status: SpecIF:LifecycleStatusReleased

## SysML:extends (SpecIF:TermStatementClass)
- dcterms:description: An [[FMC:Actor]] <> extends another [[FMC:Actor]] <>.
- SpecIF:Origin: http://specif.de
- SpecIF:Status: SpecIF:LifecycleStatusReleased

## SysML:uses (SpecIF:TermStatementClass)
- SpecIF:Origin: http://specif.de
- SpecIF:Status: SpecIF:LifecycleStatusReleased

## SysML:isAggregatedBy (SpecIF:TermStatementClass)
- dcterms:description: An [[FMC:Actor]] is aggregated by another [[FMC:Actor]].
- SpecIF:Origin: http://specif.de
- SpecIF:Status: SpecIF:LifecycleStatusReleased

## SysML:isComposedOf (SpecIF:TermStatementClass)
- dcterms:description: An [[FMC:Actor]] is composed of another [[FMC:Actor]].
- SpecIF:Origin: http://specif.de
- SpecIF:Status: SpecIF:LifecycleStatusReleased

## SysML:isAssociatedWith (SpecIF:TermStatementClass)
- dcterms:description: A [[FMC:State]] is associated with another [[FMC:State]] (e.g. a class is associated with another class, as shown in a UML Class Diagram).
- SpecIF:Origin: http://specif.de
- SpecIF:Status: SpecIF:LifecycleStatusReleased

## SysML:isAllocatedTo (SpecIF:TermStatementClass)
- dcterms:description: An [[FMC:Actor]] is allocated to another [[FMC:Actor]] (e.g. a logical function is allocated to a physical component.
- SpecIF:Origin: http://specif.de
- SpecIF:Status: SpecIF:LifecycleStatusReleased

## SpecIF:contradicts (SpecIF:TermStatementClass)
- dcterms:description: A [[IREB:Requirement]] 'contradicts' another [[IREB:Requirement]].
- SpecIF:Origin: http://specif.de
- SpecIF:Status: SpecIF:LifecycleStatusReleased

## SpecIF:duplicates (SpecIF:TermStatementClass)
- dcterms:description: A [[IREB:Requirement]] 'duplicates' another [[IREB:Requirement]].
- SpecIF:Origin: http://specif.de
- SpecIF:Status: SpecIF:LifecycleStatusReleased

## IREB:refines (SpecIF:TermStatementClass)
- dcterms:description: A [[IREB:Requirement]] refines another [[IREB:Requirement]].
- SpecIF:Origin: https://www.ireb.org/content/downloads/1-cpre-glossary/ireb_cpre_glossary_17.pdf
- SpecIF:Status: SpecIF:LifecycleStatusReleased

## SysML:isDerivedFrom (SpecIF:TermStatementClass)
- dcterms:description: A [[IREB:Requirement]] isDerivedFrom another [[IREB:Requirement]].
- SpecIF:Origin: http://specif.de
- SpecIF:Status: SpecIF:LifecycleStatusReleased

## SysML:traces (SpecIF:TermStatementClass)
- dcterms:description: A [[IREB:Requirement]] traces another [[IREB:Requirement]].
- SpecIF:Origin: http://specif.de
- SpecIF:Status: SpecIF:LifecycleStatusReleased

## SpecIF:dependsOn (SpecIF:TermStatementClass)
- dcterms:description: A [[IREB:Requirement]] 'depends on' another [[IREB:Requirement]].
- SpecIF:Origin: http://specif.de
- SpecIF:Status: SpecIF:LifecycleStatusReleased

## SpecIF:triggers (SpecIF:TermStatementClass)
- dcterms:description: A [[FMC:Event]] 'triggers' a [[FMC:Actor]].
- SpecIF:Origin: http://specif.de
- Domain: System Model Integration
- SpecIF:Status: SpecIF:LifecycleStatusDeprecated

## SpecIF:signals (SpecIF:TermStatementClass)
- dcterms:description: A [[FMC:Actor]] 'signals' a [[FMC:Event]].
- SpecIF:Origin: http://specif.de
- Domain: System Model Integration
- SpecIF:Status: SpecIF:LifecycleStatusDeprecated

## SpecIF:precedes (SpecIF:TermStatementClass)
- dcterms:description: A [[FMC:Actor]] 'precedes' a [[FMC:Actor]]; e.g. in a business process or activity flow.
- SpecIF:Origin: http://specif.de
- SpecIF:Status: SpecIF:LifecycleStatusReleased

## SpecIF:follows (SpecIF:TermStatementClass)
- dcterms:description: A [[FMC:Actor]] 'follows' a [[FMC:Actor]]; e.g. in a business process or activity flow.
- SpecIF:Origin: http://specif.de
- SpecIF:Status: SpecIF:LifecycleStatusReleased

## FMC:modifies (SpecIF:TermStatementClass)
- dcterms:description: A [[FMC:Actor]] writes _and_ reads a [[FMC:State]].
- SpecIF:Origin: http://specif.de
- SpecIF:Status: equivalent

## SpecIF:stores (SpecIF:TermStatementClass)
- dcterms:description: A [[FMC:Actor]] 'stores' (writes and reads) a [[FMC:State]].
- SpecIF:Origin: http://specif.de
- SpecIF:Status: SpecIF:LifecycleStatusReleased

## SpecIF:writes (SpecIF:TermStatementClass)
- dcterms:description: A [[FMC:Actor]] 'writes' (changes) a [[FMC:State]].
- SpecIF:Origin: http://specif.de
- SpecIF:Status: SpecIF:LifecycleStatusReleased

## SpecIF:reads (SpecIF:TermStatementClass)
- dcterms:description: A [[FMC:Actor]] 'reads' a [[FMC:State]].
- SpecIF:Origin: http://specif.de
- SpecIF:Status: SpecIF:LifecycleStatusReleased

## oslc_rm:constrainedBy (SpecIF:TermStatementClass)
- dcterms:description: The subject is constrained by the object.
- SpecIF:Origin: http://open-services.net/bin/view/Main/RmSpecificationV2

## oslc_rm:constrains (SpecIF:TermStatementClass)
- dcterms:description: The object is constrained by the subject. For example, a safety requirement constrains a functional requirement.
- SpecIF:Origin: http://open-services.net/bin/view/Main/RmSpecificationV2

## oslc_rm:decomposedBy (SpecIF:TermStatementClass)
- dcterms:description: The subject is decomposed by the object.
- SpecIF:Origin: http://open-services.net/bin/view/Main/RmSpecificationV2

## oslc_rm:decomposes (SpecIF:TermStatementClass)
- dcterms:description: The object is decomposed by the subject. For example, a collection of subsystems decomposes a system.
- SpecIF:Origin: http://open-services.net/bin/view/Main/RmSpecificationV2

## oslc_rm:validatedBy (SpecIF:TermStatementClass)
- dcterms:description: Resource, such as a test case, which validates this requirement.
- SpecIF:Origin: http://open-services.net/bin/view/Main/RmSpecificationV2

## oslc_rm:implementedBy (SpecIF:TermStatementClass)
- dcterms:description: Resource, such as a change request, which implements this requirement.
- SpecIF:Origin: http://open-services.net/bin/view/Main/RmSpecificationV2

## oslc_rm:trackedBy (SpecIF:TermStatementClass)
- dcterms:description: Resource, such as a change request, which tracks this requirement.
- SpecIF:Origin: http://open-services.net/bin/view/Main/RmSpecificationV2

## oslc_rm:affectedBy (SpecIF:TermStatementClass)
- dcterms:description: Requirement is affected by a resource, such as a defect or issue.
- SpecIF:Origin: http://open-services.net/bin/view/Main/RmSpecificationV2

## oslc_rm:specifiedBy (SpecIF:TermStatementClass)
- dcterms:description: The subject is specified by the object.
- SpecIF:Origin: http://open-services.net/bin/view/Main/RmSpecificationV2

## oslc_rm:specifies (SpecIF:TermStatementClass)
- dcterms:description: The object is specified by the subject. For example, a requirement specifies a model element.
- SpecIF:Origin: http://open-services.net/bin/view/Main/RmSpecificationV2

## oslc_rm:elaboratedBy (SpecIF:TermStatementClass)
- dcterms:description: The subject is elaborated by the object.
- SpecIF:Origin: http://open-services.net/bin/view/Main/RmSpecificationV2

## oslc_rm:elaborates (SpecIF:TermStatementClass)
- dcterms:description: The object is elaborated by the subject. For example, a use case elaborates a requirement.
- SpecIF:Origin: http://open-services.net/bin/view/Main/RmSpecificationV2

## oslc_rm:satisfiedBy (SpecIF:TermStatementClass)
- dcterms:description: The subject is satisfied by the object. For example, a user requirement is satisfied by a system requirement. (source: OSLC)
- SpecIF:Origin: http://open-services.net/bin/view/Main/RmSpecificationV2

## oslc_rm:satisfies (SpecIF:TermStatementClass)
- dcterms:description: The object is satisfied by the subject. (source: OSLC)
  SpecIF suggests that the subject is confined to a model element, e.g, a [[FMC:Actor]] or [[FMC:State]], and the object is confined to a [[IREB:Requirement]]. More concretely, an example for this type of statement is 'Component-X satisfies 'Requirement-4711'.
- SpecIF:Origin: http://open-services.net/bin/view/Main/RmSpecificationV2
- SpecIF:Status: SpecIF:LifecycleStatusReleased

## SpecIF:implements (SpecIF:TermStatementClass)
- dcterms:description: A [[FMC:Actor]] or [[FMC:State]] 'implements' a [[SpecIF:Feature]].
- SpecIF:Origin: http://specif.de
- SpecIF:Status: SpecIF:LifecycleStatusReleased

## SpecIF:satisfies (SpecIF:TermStatementClass)
- dcterms:description: A [[FMC:Actor]] or [[FMC:State]] 'satisfies' a [[IREB:Requirement]].
- SpecIF:Origin: http://specif.de
- SpecIF:Status: equivalent

## SpecIF:contains (SpecIF:TermStatementClass)
- dcterms:description: A [[FMC:Actor]] or [[FMC:State]] 'contains' a [[FMC:Actor]], [[FMC:State]] or [[FMC:Event]]. More concretely, Component-A contains Component-B.
- SpecIF:Origin: http://specif.de
- SpecIF:Status: SpecIF:LifecycleStatusReleased

## SpecIF:shows (SpecIF:TermStatementClass)
- dcterms:description: A [[SpecIF:Diagram]] 'shows' a model element, e.g, a [[FMC:Actor]], [[FMC:State]] or [[FMC:Event]].
- SpecIF:Origin: http://specif.de
- SpecIF:Status: SpecIF:LifecycleStatusReleased

## Resource Class Terms (SpecIF:Heading)
- dcterms:description: A resource represents an artefact, e.g. a model element or a requirement. The terms listed in this chapter may be used to distinguish different classes (types) of artefacts constituting a system specification. A resource may serve as subject or as object in a subject-predicate-object statement. Each resource class may define an individual set of properties for carrying the information 'payload'.
  A resource class corresponds to a 'SPEC-OBJECT-TYPE' and a resource is a 'SPEC-OBJECT' in the Requirements Interchange Format (ReqIF). In ArchiMate® 3.0, a resource is an Element.

## SpecIF:BillOfMaterials (SpecIF:TermResourceClass)
- dcterms:description: A bill of materials or product structure (sometimes bill of material, BOM or associated list) is a list of the raw materials, sub-assemblies, intermediate assemblies, sub-components, parts and the quantities of each needed to manufacture an end product. A BOM may be used for communication between manufacturing partners, or confined to a single manufacturing plant. (source: Wikipedia)
- SpecIF:Origin: http://specif.de
- SpecIF:Status: SpecIF:LifecycleStatusReleased

## SpecIF:Outline (SpecIF:TermResourceClass)
- dcterms:description: A root of a document structure with references to resources.
- SpecIF:Origin: http://specif.de
- SpecIF:Status: equivalent

## SpecIF:Hierarchy (SpecIF:TermResourceClass)
- dcterms:description: A root of a document structure with references to resources.
- SpecIF:Origin: http://specif.de
- SpecIF:Status: SpecIF:LifecycleStatusReleased

## foaf:Person (SpecIF:TermResourceClass)
- dcterms:description: The Person class represents people. Something is a Person if it is a person. We don't nitpic about whether they're alive, dead, real, or imaginary. (source: FOAF)
- SpecIF:Origin: http://xmlns.com/foaf/
- SpecIF:Status: SpecIF:LifecycleStatusReleased

## IREB:Risk (SpecIF:TermResourceClass)
- dcterms:description: An event that threatens the success of an endeavor, e.g., of developing or operating a system. A risk is typically assessed in terms of its probability and potential damage.
- SpecIF:Origin: https://www.ireb.org/content/downloads/1-cpre-glossary/ireb_cpre_glossary_17.pdf
- SpecIF:Status: SpecIF:LifecycleStatusReleased

## SpecIF:Issue (SpecIF:TermResourceClass)
- dcterms:description: An 'Issue' is a question to answer or decision to take which is worth tracking.
- SpecIF:Origin: http://specif.de
- SpecIF:Status: SpecIF:LifecycleStatusReleased

## SpecIF:Note (SpecIF:TermResourceClass)
- dcterms:description: A 'Note' is additional information by the author referring to any resource.
- SpecIF:Origin: http://specif.de
- SpecIF:Status: SpecIF:LifecycleStatusReleased

## bpmn:group (SpecIF:TermResourceClass)
- dcterms:description: BPMN: An arbitrary set of objects can be defined as a Group to show that they logically belong together. Like all BPMN 'artifacts', a group does not influence execution semantics. In PBMN, a group can be freely applied, even across pool boundaries. (source: BPMN Reference)
- SpecIF:Origin: https://camunda.com/bpmn/reference/
- SpecIF:Status: experimental

## SpecIF:Collection (SpecIF:TermResourceClass)
- dcterms:description: A 'Collection' is a logic (often conceptual) group of resources linked with a [[SpecIF:contains]] statement. It corresponds to a 'Group' in BPMN Diagrams.
  BPMN: An arbitrary set of objects can be defined as a Group to show that they logically belong together. (source: BPMN Tool)
- SpecIF:Origin: http://specif.de
- SpecIF:Status: experimental

## SpecIF:Comment (SpecIF:TermResourceClass)
- dcterms:description: A 'Comment' is reader feedback referring to any resource.
- SpecIF:Origin: http://specif.de
- SpecIF:Status: SpecIF:LifecycleStatusReleased

## SpecIF:Feature (SpecIF:TermResourceClass)
- dcterms:description: A 'Feature' is an intentional distinguishing characteristic of a system, often a unique selling proposition.
- SpecIF:Origin: http://specif.de
- SpecIF:Status: SpecIF:LifecycleStatusReleased

## IREB:Requirement (SpecIF:TermResourceClass)
- dcterms:description: A 'Requirement' is a singular documented physical and functional need that a particular design, product or process must be able to perform. (source: Wikipedia)
  Definition:
  1. A condition or capability needed by a user to solve a problem or achieve an objective.
  2. A condition or capability that must be met or possessed by a system or system component to satisfy a contract, standard, specification, or other formally imposed documents.
  3. A documented representation of a condition or capability as in (1) or (2).
  Note: The definition above is the classic one from IEEE Std 610.12 of 1990. Alternatively, we also give a more modern definition:
  1. A need perceived by a stakeholder.
  2. A capability or property that a system shall have.
  3. A documented representation of a need, capability or property.
- SpecIF:Origin: https://www.ireb.org/content/downloads/1-cpre-glossary/ireb_cpre_glossary_17.pdf
- SpecIF:Status: SpecIF:LifecycleStatusReleased

## FMC:Event (SpecIF:TermResourceClass)
- dcterms:description: An 'Event' is a fundamental model element type representing a time reference, a change in condition/value or more generally a synchronization primitive.
- SpecIF:Origin: http://fmc-modeling.org/
- SpecIF:Status: SpecIF:LifecycleStatusReleased

## FMC:State (SpecIF:TermResourceClass)
- dcterms:description: A 'State' is a fundamental model element type representing a passive entity, be it a value, a condition, an information storage or even a physical shape.
- SpecIF:Origin: http://fmc-modeling.org/
- SpecIF:Status: SpecIF:LifecycleStatusReleased

## FMC:Actor (SpecIF:TermResourceClass)
- dcterms:description: An 'Actor' is a fundamental model element type representing an active entity, be it an activity, a process step, a function, a system component or a role.
  It is advised to specify the particular use of FMC:Actor with a [[dcterms:type]] property. The values of that property can be defined terms, such as [[bpmn:timer]].
- SpecIF:Origin: http://fmc-modeling.org/
- SpecIF:Status: SpecIF:LifecycleStatusReleased

## FMC:Plan (SpecIF:TermResourceClass)
- dcterms:description: A 'Plan' is a graphical model view with a specific communication purpose, e.g. a business process or system composition.
- SpecIF:Origin: http://fmc-modeling.org/
- SpecIF:Status: equivalent

## SpecIF:View (SpecIF:TermResourceClass)
- dcterms:description: A 'View' is a graphical model view with a specific communication purpose, e.g. a business process or system composition.
- SpecIF:Origin: http://specif.de
- SpecIF:Status: SpecIF:LifecycleStatusDeprecated

## SpecIF:Diagram (SpecIF:TermResourceClass)
- dcterms:description: A 'Diagram' is a graphical model view with a specific communication purpose, e.g. a business process or system composition.
- SpecIF:Origin: http://specif.de
- SpecIF:Status: SpecIF:LifecycleStatusReleased

## SpecIF:Paragraph (SpecIF:TermResourceClass)
- dcterms:description: A 'Paragraph' is an unspecified information in a document at any level.
- SpecIF:Origin: http://specif.de
- SpecIF:Status: SpecIF:LifecycleStatusReleased

## SpecIF:Heading (SpecIF:TermResourceClass)
- dcterms:description: A 'Heading' is a chapter title at any level.
- SpecIF:Origin: http://specif.de
- SpecIF:Status: SpecIF:LifecycleStatusReleased

## Introduction (SpecIF:Heading)
- dcterms:description: The SpecIF Vocabulary (or Glossary) collects terms used in the domain of systems engineering and requirements management. Agreed-upon terms help both collaborators to communicate more clearly and systems to match data fields automatically. SpecIF adopts terms and their definitions from other initiatives, for example from the Dublin Core Metadata Initiative (DCMI), the Open Services for Lifecycle Collaboration (OSLC) and the International Requirements Engineering Board (IREB). The ProSTEP iViP association has also defined a set of attribute names to be used in ReqIF data, but those are not freely available and cannot be referenced here.
  All terms carry a namespace, which is the first part separated with ':' or '.' ― they are thus easily recognized in text and data fields. For display, systems may choose to replace SpecIF terms by domain or language specific words. This collection itself is structured according to SpecIF using it's vocabulary. Hence, the titles are recognized as such, because they are tagged with "[[dcterms:title]]", whereas paragraphs like this one are tagged with "[[dcterms:description]]".
  The terms have a lifecycle status as follows:
  - experimental: The term is being used in first projects, but has not yet any normative maturity.
  - submitted: The term has been submitted for adoption.
  - released: The term has been adopted for use with SpecIF and is preferred among equivalent terms.
  - equivalent: The term has been adopted for use with SpecIF, but the released term is preferred.
  - deprecated: The term shall not any more be used with SpecIF; use the released term.
  The Specification Interchange Facility (SpecIF) is the result of an initiative by the Gesellschaft für Systems Engineering (GfSE), the German chapter of The International Council on Systems Engineering (INCOSE).
  All information provided here is made available according to Creative Commons 4.0 CC BY-SA or the license chosen by the respective publishers. We appreciate any contribution or proposal; please contact Dr. Oskar von Dungern.
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
## SpecIF:serves (SpecIF:TermStatementClass)
- dcterms:description: A [[FMC:Actor]] 'serves' a FMC:Actor.
- SpecIF:Origin: http://specif.de
- SpecIF:Status: SpecIF:LifecycleStatusReleased

## SpecIF:hasEnumValue (SpecIF:TermStatementClass)
- dcterms:description: A property has an enumerated value.
- SpecIF:Origin: http://specif.de
- Domain: Vocabularies
- SpecIF:Status: SpecIF:LifecycleStatusSubmitted

## SpecIF:isEligibleAsSubject (SpecIF:TermStatementClass)
- dcterms:description: A resource-term statement-term is eligible as a subject of a predicate-term.

  Or concretely: A resource or statement of this class is eligible as the predicate's subject.
- SpecIF:Origin: http://specif.de
- Domain: Vocabularies
- SpecIF:Status: SpecIF:LifecycleStatusSubmitted

## SpecIF:isEligibleAsObject (SpecIF:TermStatementClass)
- dcterms:description: A resource-term or statement-term is eligible as a object of a predicate-term.

  Or concretely: A resource or statement of this class is eligible as the predicate's object.
- SpecIF:Origin: http://specif.de
- Domain: Vocabularies
- SpecIF:Status: SpecIF:LifecycleStatusSubmitted

## SpecIF:TermResourceClass (SpecIF:TermResourceClass)
- dcterms:description: A term for SpecIF resources, often used as title of a resourceClass to denote the class type.
- Domain: Vocabularies
- SpecIF:Status: experimental

## SpecIF:TermStatementClass (SpecIF:TermResourceClass)
- dcterms:description: A term for SpecIF statements, often used as title of a statementClass to denote the class type.
- Domain: Vocabularies
- SpecIF:Status: experimental

## SpecIF:TermProperty (SpecIF:TermResourceClass)
- dcterms:description: A term for SpecIF properties, often used as title of a propertyClass to denote the class type.
- Domain: Vocabularies
- SpecIF:Status: experimental

## SpecIF:TermPropertyValue (SpecIF:TermResourceClass)
- dcterms:description: A term for SpecIF property values, often used in enumerated dataTypes.
- Domain: Vocabularies
- SpecIF:Status: experimental

## SpecIF:sendsTo (SpecIF:TermStatementClass)
- dcterms:description: A [[FMC:Actor]] 'sends' a message to a [[FMC:Actor]].
- SpecIF:Origin: http://specif.de
- Domain: System Model Integration
- SpecIF:Status: SpecIF:LifecycleStatusReleased

## SpecIF:receivesFrom (SpecIF:TermStatementClass)
- dcterms:description: A [[FMC:Actor]] 'receives' a message from a [[FMC:Actor]].
- SpecIF:Origin: http://specif.de
- Domain: System Model Integration
- SpecIF:Status: SpecIF:LifecycleStatusReleased

## SpecIF:communicatesWith (SpecIF:TermStatementClass)
- dcterms:description: A [[FMC:Actor]] 'communicates' with a [[FMC:Actor]].
- SpecIF:Origin: http://specif.de
- Domain: System Model Integration
- SpecIF:Status: SpecIF:LifecycleStatusReleased

## SpecIF:influences (SpecIF:TermStatementClass)
- dcterms:description: The influence relationship represents that an element affects the implementation or achievement of some motivation element.
- SpecIF:Origin: https://pubs.opengroup.org/architecture/archimate3-doc/chap05.html
- Domain: System Model Integration
- SpecIF:Status: experimental

## SysML:isSpecialisationOf (SpecIF:TermStatementClass)
- dcterms:description: An FMC:Actor is a specialization of another FMC:Actor; similarly for FMC:State and FMC:Event.
- SpecIF:Origin: http://specif.de
- Domain: Vocabularies
- SpecIF:Status: SpecIF:LifecycleStatusDeprecated

## SysML:isGeneralisationOf (SpecIF:TermStatementClass)
- dcterms:description: An FMC:Actor is a generalization of another FMC:Actor; similarly for FMC:State and FMC:Event.
- SpecIF:Origin: http://specif.de
- Domain: Vocabularies
- SpecIF:Status: SpecIF:LifecycleStatusDeprecated

## Statements
- FMC:Plan SpecIF:isSynonymOf SpecIF:Diagram
- SpecIF:View SpecIF:isSynonymOf SpecIF:Diagram
- SpecIF:Collection SpecIF:isSynonymOf bpmn:group
- SpecIF:satisfies SpecIF:isSynonymOf oslc_rm:satisfies
- SpecIF:Stereotype SpecIF:isSynonymOf dcterms:type
- SpecIF:SubClass SpecIF:isSynonymOf dcterms:type
- oslc_rm:satisfiedBy SpecIF:isAntonymOf oslc_rm:satisfies
- oslc_rm:elaboratedBy SpecIF:isAntonymOf oslc_rm:elaborates
- oslc_rm:specifiedBy SpecIF:isAntonymOf oslc_rm:specifies
- oslc_rm:decomposedBy SpecIF:isAntonymOf oslc_rm:decomposes
- oslc_rm:constrainedBy SpecIF:isAntonymOf oslc_rm:constrains
- SpecIF:follows SpecIF:isAntonymOf SpecIF:precedes
- SysML:isGeneralizationOf SpecIF:isAntonymOf SysML:isSpecializationOf
- SpecIF:sameAs SpecIF:isSynonymOf owl:sameAs
- SpecIF:Outline SpecIF:isSynonymOf SpecIF:Hierarchy
- SpecIF:Id SpecIF:isSynonymOf dcterms:identifier
- SpecIF:createdBy SpecIF:isSynonymOf dcterms:creator
- SpecIF:createdAt SpecIF:isSynonymOf dcterms:created
- SpecIF:changedAt SpecIF:isSynonymOf dcterms:modified
- SpecIF:Creation SpecIF:isSynonymOf SpecIF:Instantiation
- SpecIF:Source SpecIF:isSynonymOf SpecIF:Subject
- SpecIF:Target SpecIF:isSynonymOf SpecIF:Object
- IREB:RequirementTypeFunction SpecIF:isSynonymOf IREB:FunctionalRequirement
- IREB:RequirementTypeQuality SpecIF:isSynonymOf IREB:QualityRequirement
- IREB:RequirementTypeConstraint SpecIF:isSynonymOf IREB:Constraint
- SpecIF:isInverseOf SpecIF:isSynonymOf SpecIF:isAntonymOf
- SysML:isComposedOf SpecIF:isSpecializationOf SpecIF:contains
- SysML:isAggregatedBy SpecIF:isSpecializationOf SpecIF:contains
- FMC:modifies SpecIF:isSynonymOf SpecIF:stores
- SpecIF:Stereotype SpecIF:isSynonymOf UML:Stereotype
- UML:Stereotype SpecIF:isSynonymOf dcterms:type
- SpecIF:SubClass SpecIF:isSynonymOf UML:Stereotype
- SpecIF:Priority SpecIF:hasEnumValue SpecIF:priorityHigh
- SpecIF:Priority SpecIF:hasEnumValue SpecIF:priorityRatherHigh
- SpecIF:Priority SpecIF:hasEnumValue SpecIF:priorityMedium
- SpecIF:Priority SpecIF:hasEnumValue SpecIF:priorityRatherLow
- SpecIF:Priority SpecIF:hasEnumValue SpecIF:priorityLow
- FMC:Actor SpecIF:isEligibleAsSubject SpecIF:reads
- FMC:State SpecIF:isEligibleAsObject SpecIF:reads
- FMC:Actor SpecIF:isEligibleAsSubject SpecIF:writes
- FMC:State SpecIF:isEligibleAsObject SpecIF:writes
- FMC:Actor SpecIF:isEligibleAsSubject SpecIF:stores
- FMC:State SpecIF:isEligibleAsObject SpecIF:stores
- SpecIF:signals SpecIF:isSpecializationOf SpecIF:precedes
- SpecIF:triggers SpecIF:isSpecializationOf SpecIF:precedes
- SpecIF:receivesFrom SpecIF:isAntonymOf SpecIF:sendsTo
- SpecIF:sendsTo SpecIF:isSpecializationOf SpecIF:communicatesWith
- SpecIF:receivesFrom SpecIF:isSpecializationOf SpecIF:communicatesWith
- FMC:Actor SpecIF:isEligibleAsSubject SpecIF:serves
- FMC:Actor SpecIF:isEligibleAsObject SpecIF:serves
- SysML:isSpecialisationOf SpecIF:isSynonymOf SysML:isSpecializationOf
- SysML:isGeneralisationOf SpecIF:isSynonymOf SysML:isGeneralizationOf
